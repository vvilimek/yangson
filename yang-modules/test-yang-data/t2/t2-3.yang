module t2-3 {

  yang-version "1.1";

  namespace "http://example.com/t2-3";

  prefix "t";

  import ietf-restconf {
    prefix "rc";
    revision-date 2017-01-26;
  }

  rc:yang-data ydata {
    container data {
      // xpath reference outside context (we are locked inside ydata)
      must "../../data2/leafA > 2";
    }
  }

  rc:yang-data ydata2 {
    container data2 {
      leaf leafA {
        type int32;
      }
    }
  }
}
