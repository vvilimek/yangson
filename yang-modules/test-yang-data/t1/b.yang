module b {

  yang-version "1.1";

  namespace "http://example.com/b";

  prefix "b";

  import defs {
    prefix "d";
  }

  identity b-derived {
    base d:ident-base;
  }

  leaf inaccessible {
    type string;
  }
}
